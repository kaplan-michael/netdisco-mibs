-- ZyXEL Communications Corporation
-- Private Enterprise MIB definition 
  
-- This file describes the ZyXEL Communications Corporation Enterprise MIB.
-- It contains ZyXEL products OIDs, and common managed objects.

-- ZYXEL-IPV6-SNOOPING-MIB.mib
-- Revision 1.1  2015/01/28 

ZYXEL-IPV6-SNOOPING-MIB DEFINITIONS ::= BEGIN


    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC
	  	
	EnabledStatus
		FROM  P-BRIDGE-MIB
	
	esMgmt			
		FROM ZYXEL-ES-SMI;

	zyxelIpv6Snooping MODULE-IDENTITY
		LAST-UPDATED	"201412310000Z"    
		ORGANIZATION "Enterprise Solution ZyXEL"     
		CONTACT-INFO
			""	   
		DESCRIPTION
			"The subtree for IPv6 snooping"
		::= { esMgmt 109 }

	zyxelIpv6SnoopingSetup 	OBJECT IDENTIFIER ::= { zyxelIpv6Snooping 1 }		


	zyIpv6SnoopingPolicyMaxNumberOfPolicies OBJECT-TYPE
        SYNTAX  	INTEGER
        MAX-ACCESS  read-only
        STATUS  	current
        DESCRIPTION
		"The maximum number of IPv6 snooping policy entries that can be created."
		::= { zyxelIpv6SnoopingSetup 1 } 
		
	zyxelIpv6SnoopingPolicyTable OBJECT-TYPE
        SYNTAX	SEQUENCE OF ZyxelIpv6SnoopingPolicyEntry
        MAX-ACCESS  not-accessible
        STATUS  current
        DESCRIPTION
        "The table maintains IPv6 snooping policy configuration."
        ::= { zyxelIpv6SnoopingSetup 2 }
        
	zyxelIpv6SnoopingPolicyEntry OBJECT-TYPE
        SYNTAX	ZyxelIpv6SnoopingPolicyEntry
        MAX-ACCESS	not-accessible
        STATUS	current
        DESCRIPTION    	
		"An entry contains IPv6 snooping policy configuration."
        INDEX          	{ zyIpv6SnoopingPolicyName }
        ::= { zyxelIpv6SnoopingPolicyTable 1 }              

      	ZyxelIpv6SnoopingPolicyEntry ::=
		SEQUENCE {
        	zyIpv6SnoopingPolicyName						DisplayString,
        	zyIpv6SnoopingPolicyProtocol					BITS,
        	zyIpv6SnoopingPolicyPrefixGleanState			EnabledStatus,
        	zyIpv6SnoopingPolicyLimitAddressCount			INTEGER,
          	zyIpv6SnoopingPolicyRowStatus 					RowStatus
           }

        zyIpv6SnoopingPolicyName OBJECT-TYPE
        SYNTAX  DisplayString
        MAX-ACCESS  not-accessible
        STATUS  current
        DESCRIPTION
        "The name of IPv6 snooping policy."
        ::= { zyxelIpv6SnoopingPolicyEntry 1 }

        zyIpv6SnoopingPolicyProtocol OBJECT-TYPE
        SYNTAX  BITS {
        	dhcp(0)
        }
        MAX-ACCESS  read-write
        STATUS  current
        DESCRIPTION
        "Select the protocol is snooped in the policy."
        ::= { zyxelIpv6SnoopingPolicyEntry 2 }                        

        zyIpv6SnoopingPolicyPrefixGleanState OBJECT-TYPE
        SYNTAX  EnabledStatus
        MAX-ACCESS  read-write
        STATUS  current
        DESCRIPTION
        "Enable/Disable the option to glean IPv6 prefix in DHCP-PD packet"
        ::= { zyxelIpv6SnoopingPolicyEntry 3 }                        

        zyIpv6SnoopingPolicyLimitAddressCount OBJECT-TYPE
        SYNTAX  INTEGER
        MAX-ACCESS  read-write
        STATUS  current
        DESCRIPTION
        "Set this field to limit the number of snooped addresses. 
        For example, if you set this field to 5, then only the devices 
        with these five learned addresses may snooped on the policy at any one time. 
        A sixth device would have to wait until one of the five learned addresses aged out. 
        0 means no limit."
        ::= { zyxelIpv6SnoopingPolicyEntry 4 }                        

        zyIpv6SnoopingPolicyRowStatus OBJECT-TYPE
        SYNTAX  RowStatus
        MAX-ACCESS  read-write
        STATUS  current
        DESCRIPTION
        "This object allows an IPv6 snooping policy entry to be created and deleted."
        ::= { zyxelIpv6SnoopingPolicyEntry 100 }
		

		zyxelIpv6SnoopingPolicyIfTable OBJECT-TYPE
        SYNTAX	SEQUENCE OF ZyxelIpv6SnoopingPolicyIfEntry
        MAX-ACCESS  not-accessible
        STATUS  current
        DESCRIPTION
        "The table maintains IPv6 snooping policy interface VLAN configuration"
        ::= { zyxelIpv6SnoopingSetup 3 }
                               
		zyxelIpv6SnoopingPolicyIfEntry OBJECT-TYPE
        SYNTAX	ZyxelIpv6SnoopingPolicyIfEntry
        MAX-ACCESS	not-accessible
        STATUS	current
        DESCRIPTION    	
		"An entry contains IPv6 snooping policy interface VLAN configuration."
        INDEX          	{ zyIpv6SnoopingPolicyIfIndex }
        ::= { zyxelIpv6SnoopingPolicyIfTable 1 }              

      	ZyxelIpv6SnoopingPolicyIfEntry ::=
		SEQUENCE {
         	zyIpv6SnoopingPolicyIfIndex				INTEGER,
			zyIpv6SnoopingPolicyIfAttachPolicy		DisplayString
           }

        zyIpv6SnoopingPolicyIfIndex OBJECT-TYPE
        SYNTAX  INTEGER
        MAX-ACCESS  not-accessible
        STATUS  current
        DESCRIPTION
        "The interface VLAN of IPv6. It is created by zyxelIf module."
        ::= { zyxelIpv6SnoopingPolicyIfEntry 1 }

        zyIpv6SnoopingPolicyIfAttachPolicy OBJECT-TYPE
        SYNTAX  DisplayString
        MAX-ACCESS  read-write
        STATUS  current
        DESCRIPTION
        "Select the policy attach to the interface VLAN."
        ::= { zyxelIpv6SnoopingPolicyIfEntry 2 }                        
                          
END
