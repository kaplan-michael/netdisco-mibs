-- ZyXEL Communications Corporation
-- Private Enterprise MIB definition 
  
-- This file describes the ZyXEL Communications Corporation Enterprise MIB.
-- It contains ZyXEL products OIDs, and common managed objects.

-- ZYXEL-REMOTE-PORT-MIRROR-MIB.mib
-- Revision 1.7  2013/12/06 

ZYXEL-REMOTE-PORT-MIRROR-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579

	EnabledStatus
		FROM  P-BRIDGE-MIB
	
	PortList
		FROM  Q-BRIDGE-MIB

	esMgmt			
		FROM ZYXEL-ES-SMI;

	zyxelRemotePortMirror MODULE-IDENTITY
		LAST-UPDATED	"201207010000Z"    
		ORGANIZATION "Enterprise Solution ZyXEL"     
		CONTACT-INFO
			""	   
		DESCRIPTION
			"The subtree for remote port mirror"
		::= { esMgmt 73 }
		
	zyxelRemotePortMirrorSetup	OBJECT IDENTIFIER ::= { zyxelRemotePortMirror 1 }
  
-- *******************************************************************
-- *
-- * zyxelRemotePortMirrorSetup
-- *
-- *******************************************************************

-- zyxelRemotePortMirrorMaxNumberOfVlans	
		zyRemotePortMirrorMaxNumberOfVlans OBJECT-TYPE
        SYNTAX  INTEGER
        MAX-ACCESS  read-only
        STATUS  current
        DESCRIPTION
			"The maximum number of remote mirror VLAN entries that can be created."
        ::= { zyxelRemotePortMirrorSetup 1 }
		
-- zyxelRemotePortMirrorTable		
        zyxelRemotePortMirrorTable OBJECT-TYPE
        SYNTAX	SEQUENCE OF ZyxelRemotePortMirrorEntry
        MAX-ACCESS  not-accessible
        STATUS  current
        DESCRIPTION
			"The table contains remote port mirror configuration."
        ::= { zyxelRemotePortMirrorSetup 2 }

		zyxelRemotePortMirrorEntry OBJECT-TYPE
        SYNTAX	ZyxelRemotePortMirrorEntry
        MAX-ACCESS	not-accessible
        STATUS	current
        DESCRIPTION    	
			"An entry contains remote port mirror configuration. "
        INDEX          	{ zyRemotePortMirrorVid }
        ::= { zyxelRemotePortMirrorTable 1 }
		
		
        ZyxelRemotePortMirrorEntry ::=
		SEQUENCE {
        	zyRemotePortMirrorVid							INTEGER,
			zyRemotePortMirrorSource8021pPriority			INTEGER,
        	zyRemotePortMirrorSourceIngressMirrorPorts		PortList,
        	zyRemotePortMirrorSourceEgressMirrorPorts		PortList,
			zyRemotePortMirrorSourceReflectorPortState		EnabledStatus,     
			zyRemotePortMirrorSourceReflectorPort			INTEGER,
        	zyRemotePortMirrorDestinationMonitorPort		INTEGER, 
        	zyRemotePortMirrorDestinationMonitorPortTagging	EnabledStatus,
			zyRemotePortMirrorConnectedPorts				PortList,
			zyRemotePortMirrorRowStatus						RowStatus        	
        }

        zyRemotePortMirrorVid OBJECT-TYPE
        SYNTAX  INTEGER(1..4094)
        MAX-ACCESS  not-accessible
        STATUS  current
        DESCRIPTION
			"Enter the VLAN ID (1 to 4094) of the remote mirror VLAN. "
        ::= { zyxelRemotePortMirrorEntry 1 }

		zyRemotePortMirrorSource8021pPriority OBJECT-TYPE
        SYNTAX  INTEGER(0..7)
        MAX-ACCESS  read-write
        STATUS  current
        DESCRIPTION
			"Select a priority level (0-7) with which the Switch replaces the priority of packets from source 
			port (belonging to this remote mirror VLAN). "
        ::= { zyxelRemotePortMirrorEntry 2 }

		zyRemotePortMirrorSourceIngressMirrorPorts OBJECT-TYPE
        SYNTAX  PortList
        MAX-ACCESS  read-write
        STATUS  current
        DESCRIPTION
			"Set port members to be the source ingress mirror-port. 
				The mirror-port is the port traffic that we mirrored:
				1. Mirror-ports is only existed in source switch.
				2. It can be any port type, such as Ether Channel, Fast Ethernet, Gigabit Ethernet, and so forth.
				3. It can be monitored in multiple remote mirror VLAN.
				4. It cannot be a monitor-port, reflector-port and connected-port."
        ::= { zyxelRemotePortMirrorEntry 3 }

		zyRemotePortMirrorSourceEgressMirrorPorts OBJECT-TYPE
        SYNTAX  PortList
        MAX-ACCESS  read-write
        STATUS  current
        DESCRIPTION
			"Set port members to be the source egress mirror-port. 
				The mirror-port is the port traffic that we mirrored:
				1. Mirror-ports is only existed in source switch.
				2. It can be any port type, such as Ether Channel, Fast Ethernet, Gigabit Ethernet, and so forth.
				3. It can be monitored in multiple remote mirror VLAN.
				4. It cannot be a monitor-port, reflector-port and connected-port."
        ::= { zyxelRemotePortMirrorEntry 4 }
		
		zyRemotePortMirrorSourceReflectorPortState OBJECT-TYPE
        SYNTAX  EnabledStatus
        MAX-ACCESS  read-write
        STATUS  current
        DESCRIPTION
			"Enable/disable multi-mirroring on RMirror Source.
				Once the multi-mirroring is enabled, the reflector-port can be used in the RMirrore Source."
        ::= { zyxelRemotePortMirrorEntry 5 }
		
		zyRemotePortMirrorSourceReflectorPort OBJECT-TYPE
        SYNTAX  INTEGER
        MAX-ACCESS  read-write
        STATUS  current
        DESCRIPTION
			"Set port members to be the source reflector-port. 
				The reflector port is the mechanism that copies packets onto an remote mirror VLAN. 
				The reflector port forwards only traffic from remote mirror VLAN with which it is affiliated:
				1. A reflector-port is only existed in source switch.
				2. Spanning tree is automatically disabled on a reflector-port.
				3. It is a port set to loopback. 
				4. The reflector port loops back untagged traffic to the switch. 
				   The traffic is then placed on the RSPAN VLAN and flooded to any trunk ports that carry the RSPAN VLAN.
				5. The reflector-port can not be mirror-port and monitor-port."
        ::= { zyxelRemotePortMirrorEntry 6 }

		zyRemotePortMirrorDestinationMonitorPort OBJECT-TYPE
        SYNTAX  INTEGER
        MAX-ACCESS  read-write
        STATUS  current
        DESCRIPTION
			"Set the port number of the destination monitor port. 
				The monitor-port is the port that we can monitor the RMirror traffic:
				1. A monitor-port is only in destination switch. 
				2. It can participate in only one RMirror VLAN at a time.
				3. A monitor-port in one RMirror VLAN cannot be another RMirror VLAN.
				4. A monitor-port can not be a mirror-port, reflector-port and connected-port."
        ::= { zyxelRemotePortMirrorEntry 7 }

	    zyRemotePortMirrorDestinationMonitorPortTagging OBJECT-TYPE
	        SYNTAX      EnabledStatus
	        MAX-ACCESS  read-write
	        STATUS      current
	        DESCRIPTION
	         "Enable/Disable the destination monitor port which packet with tag."
	    ::= { zyxelRemotePortMirrorEntry 8 }

		zyRemotePortMirrorConnectedPorts OBJECT-TYPE
        SYNTAX  PortList
        MAX-ACCESS  read-write
        STATUS  current
        DESCRIPTION
			"Set port members to be the connected-port. 
				The connected-port is the physical port connected to other switch in the same remote mirror VLAN:
				1. The port must join the remote mirror VLAN.
				2. The connected-port can not be mirror-port and monitor-port."
        ::= { zyxelRemotePortMirrorEntry 9 }

		zyRemotePortMirrorRowStatus OBJECT-TYPE
        SYNTAX  RowStatus
        MAX-ACCESS  read-create
        STATUS  current
        DESCRIPTION
			"This object allows entries to be created and deleted from the remote mirror table."
        ::= { zyxelRemotePortMirrorEntry 10 }
		

END
