-- ZyXEL Communications Corporation
-- Private Enterprise MIB definition 
  
-- This file describes the ZyXEL Communications Corporation Enterprise MIB.
-- It contains ZyXEL products OIDs, and common managed objects.

-- ZYXEL-SYS-MEMORY-MIB.mib
-- Revision 1.4  2013/12/06 

ZYXEL-SYS-MEMORY-MIB DEFINITIONS ::= BEGIN

    IMPORTS
	OBJECT-TYPE
		FROM SNMPv2-SMI			-- RFC2578	
		
	MODULE-IDENTITY
		FROM SNMPv2-SMI
	
	Unsigned32
		FROM SNMPv2-SMI

	esMgmt			
		FROM ZYXEL-ES-SMI;

	zyxelSysMemory MODULE-IDENTITY
		LAST-UPDATED	"201207010000Z"    
		ORGANIZATION "Enterprise Solution ZyXEL"     
		CONTACT-INFO
			""	   
		DESCRIPTION
			"The subtree for system memory"
		::= { esMgmt 50 }	

	zyxelSysMemoryPoolStatus	OBJECT IDENTIFIER ::= { zyxelSysMemory 1 }
                      
        
		zyxelSysMemoryPoolTable OBJECT-TYPE
	    SYNTAX      SEQUENCE OF ZyxelSysMemoryPoolEntry
	    MAX-ACCESS  not-accessible
	    STATUS      current
	    DESCRIPTION
	    	"The table that show memory utilization statistics on the switch."              
    	::= { zyxelSysMemoryPoolStatus 1 } 
    	    
    	zyxelSysMemoryPoolEntry OBJECT-TYPE
        SYNTAX      ZyxelSysMemoryPoolEntry
        MAX-ACCESS  not-accessible
        STATUS      current
        DESCRIPTION
            "Memory utilization statistics information for the switch."
        INDEX {zySysMemoryPoolId }
    	::= { zyxelSysMemoryPoolTable 1 }
    
    	ZyxelSysMemoryPoolEntry ::=
        SEQUENCE {
            zySysMemoryPoolId       		Unsigned32, 
            zySysMemoryPoolName     		OCTET STRING,
            zySysMemoryPoolTotalSize  		Unsigned32, 
            zySysMemoryPoolUsedSize   		Unsigned32,
            zySysMemoryPoolUtilization    	Unsigned32
        } 
    
    	zySysMemoryPoolId OBJECT-TYPE
        SYNTAX      Unsigned32
        MAX-ACCESS  not-accessible
        STATUS      current
        DESCRIPTION
        	"ID of the memory pool."
    	::= { zyxelSysMemoryPoolEntry 1 }
    
    	zySysMemoryPoolName OBJECT-TYPE
        SYNTAX      OCTET STRING(SIZE (0..32))
        MAX-ACCESS  read-only
        STATUS      current
        DESCRIPTION
        	"Name of the memory pool."
    	::= { zyxelSysMemoryPoolEntry 2 }
        
    	zySysMemoryPoolTotalSize OBJECT-TYPE
        SYNTAX      Unsigned32
        MAX-ACCESS  read-only
        STATUS      current
        DESCRIPTION
        	"Total size of memory pool in bytes."
    	::= { zyxelSysMemoryPoolEntry 3 }
    
   		zySysMemoryPoolUsedSize OBJECT-TYPE
        SYNTAX      Unsigned32
        MAX-ACCESS  read-only
        STATUS      current
        DESCRIPTION
        	"Used size of memory pool in bytes."
    	::= { zyxelSysMemoryPoolEntry 4 }
    
    	zySysMemoryPoolUtilization OBJECT-TYPE
        SYNTAX      Unsigned32 (0..100)
        MAX-ACCESS  read-only
        STATUS      current
        DESCRIPTION
        	"Utilization of memory pool in bytes."
    	::= { zyxelSysMemoryPoolEntry 5 }

END
