-- ZyXEL Communications Corporation
-- Private Enterprise MIB definition 
  
-- This file describes the ZyXEL Communications Corporation Enterprise MIB.
-- It contains ZyXEL products OIDs, and common managed objects.

-- ZYXEL-FDB-MIB.mib
-- Revision 1.5  2013/12/06 

ZYXEL-FDB-MIB DEFINITIONS ::= BEGIN
    
    IMPORTS
	OBJECT-TYPE
		FROM SNMPv2-SMI			-- RFC2578	
		
	MODULE-IDENTITY
		FROM SNMPv2-SMI
	
	EnabledStatus
		FROM  P-BRIDGE-MIB

	NOTIFICATION-TYPE
		FROM SNMPv2-SMI

	esMgmt			
		FROM ZYXEL-ES-SMI;

	zyxelFdb MODULE-IDENTITY
		LAST-UPDATED	"201207010000Z"    
		ORGANIZATION "Enterprise Solution ZyXEL"     
		CONTACT-INFO
			""	   
		DESCRIPTION
			"The subtree for forwarding and/or filtering database"
		::= { esMgmt 48 }
		
	zyxelMacStatus	     		OBJECT IDENTIFIER ::= { zyxelFdb 1 }
	zyxelMacStatusNotifications	OBJECT IDENTIFIER ::= { zyxelFdb 2 }

	                     
        
        zyMacFlush OBJECT-TYPE
        SYNTAX  EnabledStatus
        MAX-ACCESS  read-write
        STATUS  current
        DESCRIPTION
			"Active to clear the MAC address table."
        ::= { zyxelMacStatus 1 }

        zyMacFlushPort OBJECT-TYPE
        SYNTAX  INTEGER
        MAX-ACCESS  read-write
        STATUS  current
        DESCRIPTION
			"Clear all learned MAC address on the specified port."
        ::= { zyxelMacStatus 2 }

        zyMacFlushVlan OBJECT-TYPE
        SYNTAX  INTEGER
        MAX-ACCESS  read-write
        STATUS  current
        DESCRIPTION
			"Clear all learned MAC address on the specified VLAN."
        ::= { zyxelMacStatus 3 }  
        
	   zyMacForwardingTableFull NOTIFICATION-TYPE
	   STATUS  current
       DESCRIPTION
               "MAC address switching table has become full."
       ::= { zyxelMacStatusNotifications 1 }        
        
	   zyMacForwardingTableFullRecovered NOTIFICATION-TYPE
	   STATUS  current
       DESCRIPTION
               "MAC address switching table has recovered from full."
       ::= { zyxelMacStatusNotifications 2 }        
                                             
END
