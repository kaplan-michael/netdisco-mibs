-- ZyXEL Communications Corporation
-- Private Enterprise MIB definition 
  
-- This file describes the ZyXEL Communications Corporation Enterprise MIB.
-- It contains ZyXEL products OIDs, and common managed objects.

-- ZYXEL-IGMP-FILTER-MIB.mib
-- Revision 1.4  2013/12/06 

ZYXEL-IGMP-FILTER-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC
	 
	EnabledStatus
		FROM  P-BRIDGE-MIB
		

	dot1dBasePort
	   	FROM BRIDGE-MIB
	
		IpAddress
			FROM SNMPv2-SMI

	esMgmt			
		FROM ZYXEL-ES-SMI;

	zyxelIgmpFilter MODULE-IDENTITY
		LAST-UPDATED	"201207010000Z"    
		ORGANIZATION "Enterprise Solution ZyXEL"     
		CONTACT-INFO
			""	   
		DESCRIPTION
			"The subtree for Internet Group Management Protocol (IGMP) filter"
		::= { esMgmt 30 }
			
	zyxelIgmpFilteringSetup	OBJECT IDENTIFIER ::= { zyxelIgmpFilter 1 }		

-- 	1.zyxelIgmpFilteringProfileSetup 
        zyIgmpFilteringState OBJECT-TYPE
        SYNTAX  EnabledStatus
        MAX-ACCESS  read-write
        STATUS  current
        DESCRIPTION
        "Enable/Disable IGMP filtering on the switch. An IGMP filtering profile specifies 
		 a range of multicast groups that clients connected to the switch are able to join."
        ::= { zyxelIgmpFilteringSetup 1 }

		zyIgmpFilteringMaxNumberOfProfiles OBJECT-TYPE
        SYNTAX  INTEGER
        MAX-ACCESS  read-only
        STATUS  current
        DESCRIPTION
        "The maximum number of IGMP filtering profile entries that can be created."
        ::= { zyxelIgmpFilteringSetup 2 }
	
        zyxelIgmpFilteringProfileTable	OBJECT-TYPE
        SYNTAX	SEQUENCE OF ZyxelIgmpFilteringProfileEntry
        MAX-ACCESS  not-accessible
        STATUS  current
        DESCRIPTION
        "The table contains IGMP filtering profile configuration."
        ::= { zyxelIgmpFilteringSetup 3 }
        
		zyxelIgmpFilteringProfileEntry OBJECT-TYPE
        SYNTAX	ZyxelIgmpFilteringProfileEntry
        MAX-ACCESS	not-accessible
        STATUS	current
        DESCRIPTION    	
		"An entry contains IGMP filtering profile configuration."
        INDEX          	{ zyIgmpFilteringProfileName, zyIgmpFilteringProfileStartIpAddress, zyIgmpFilteringProfileEndIpAddress }
        ::= { zyxelIgmpFilteringProfileTable 1 }

        ZyxelIgmpFilteringProfileEntry ::=
		SEQUENCE {
        	zyIgmpFilteringProfileName				DisplayString,
        	zyIgmpFilteringProfileStartIpAddress	IpAddress,
        	zyIgmpFilteringProfileEndIpAddress		IpAddress,
        	zyIgmpFilteringProfileRowStatus			RowStatus
        }

        zyIgmpFilteringProfileName OBJECT-TYPE
        SYNTAX  DisplayString
        MAX-ACCESS  not-accessible
        STATUS  current
        DESCRIPTION
        "A descriptive name for the profile for identification purposes."
        ::= { zyxelIgmpFilteringProfileEntry 1 }

        zyIgmpFilteringProfileStartIpAddress OBJECT-TYPE
        SYNTAX  IpAddress
        MAX-ACCESS  not-accessible
        STATUS  current
        DESCRIPTION
        "The starting multicast IP address for a range of multicast IP addresses 
		 that you want to belong to the IGMP filter profile."
        ::= { zyxelIgmpFilteringProfileEntry 2 }

        zyIgmpFilteringProfileEndIpAddress OBJECT-TYPE
        SYNTAX  IpAddress
        MAX-ACCESS  not-accessible
        STATUS  current
        DESCRIPTION
        "The ending multicast IP address for a range of IP addresses that you want to belong to the IGMP filter profile."
        ::= { zyxelIgmpFilteringProfileEntry 3 }
        
        zyIgmpFilteringProfileRowStatus OBJECT-TYPE
        SYNTAX  RowStatus
        MAX-ACCESS  read-create
        STATUS  current
        DESCRIPTION
        "This object allow IGMP filtering profile entries to be create and deleted from IGMP filtering profile table."
        ::= { zyxelIgmpFilteringProfileEntry 4 }


        zyxelIgmpFilteringPortTable	OBJECT-TYPE
        SYNTAX	SEQUENCE OF ZyxelIgmpFilteringPortEntry
        MAX-ACCESS  not-accessible
        STATUS  current
        DESCRIPTION
        "The table contains IGMP filtering port configuration. "
        ::= { zyxelIgmpFilteringSetup 4 }
        
		zyxelIgmpFilteringPortEntry OBJECT-TYPE
        SYNTAX	ZyxelIgmpFilteringPortEntry
        MAX-ACCESS	not-accessible
        STATUS	current
        DESCRIPTION    	
		"An entry contains IGMP filtering port configuration. "
        INDEX          	{ dot1dBasePort }
        ::= { zyxelIgmpFilteringPortTable 1 }

        ZyxelIgmpFilteringPortEntry ::=
		SEQUENCE {
        	zyIgmpFilteringPortProfile	DisplayString 	
        }       
        
        zyIgmpFilteringPortProfile OBJECT-TYPE
        SYNTAX  DisplayString
        MAX-ACCESS  read-write
        STATUS  current
        DESCRIPTION
        "Enter the name of the IGMP filtering profile to use for this port. "
        ::= { zyxelIgmpFilteringPortEntry 1 }        

END
