-- ZyXEL Communications Corporation
-- Private Enterprise MIB definition 
  
-- This file describes the ZyXEL Communications Corporation Enterprise MIB.
-- It contains ZyXEL products OIDs, and common managed objects.

-- ZYXEL-PORT-BASED-VLAN-MIB.mib
-- Revision 1.4  2013/12/06 

ZYXEL-PORT-BASED-VLAN-MIB DEFINITIONS ::= BEGIN

    IMPORTS
	OBJECT-TYPE
		FROM SNMPv2-SMI			-- RFC2578	
		
	MODULE-IDENTITY
		FROM SNMPv2-SMI
		
	PortList
		FROM  Q-BRIDGE-MIB
		
	dot1dBasePort
       	FROM BRIDGE-MIB

	esMgmt			
		FROM ZYXEL-ES-SMI;

	zyxelPortBasedVlan MODULE-IDENTITY
		LAST-UPDATED	"201207010000Z"    
		ORGANIZATION "Enterprise Solution ZyXEL"     
		CONTACT-INFO
			""	   
		DESCRIPTION
			"The subtree for port-based VLAN"
		::= { esMgmt 63 }
		
	zyxelPortBasedVlanSetup OBJECT IDENTIFIER ::= { zyxelPortBasedVlan 1 }


                                                            
-- 		zyxelPortBasedVlanTable 

        zyxelPortBasedVlanTable  OBJECT-TYPE
        SYNTAX	SEQUENCE OF ZyxelPortBasedVlanEntry 
        MAX-ACCESS  not-accessible
        STATUS  current
        DESCRIPTION
                 	"The table contains port-based VLAN configuration. "
        ::= { zyxelPortBasedVlanSetup 1 }
        
		zyxelPortBasedVlanEntry  OBJECT-TYPE
        SYNTAX	ZyxelPortBasedVlanEntry 
        MAX-ACCESS	not-accessible
        STATUS	current
        DESCRIPTION    	"An entry contains port-based VLAN configuration. "
        INDEX          	{ dot1dBasePort }
        ::= { zyxelPortBasedVlanTable 1 }

        ZyxelPortBasedVlanEntry ::=
           SEQUENCE {
        	zyPortBasedVlanPorts	OCTET STRING
           }

        zyPortBasedVlanPorts OBJECT-TYPE
        SYNTAX  PortList
        MAX-ACCESS  read-write
        STATUS  current
        DESCRIPTION
                      	"Set port members for each port. This allows packets to be forwarded to these port members. "
        ::= { zyxelPortBasedVlanEntry 1 }
END
