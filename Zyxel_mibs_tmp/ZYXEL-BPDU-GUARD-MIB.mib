-- ZyXEL Communications Corporation
-- Private Enterprise MIB definition 
  
-- This file describes the ZyXEL Communications Corporation Enterprise MIB.
-- It contains ZyXEL products OIDs, and common managed objects.

-- ZYXEL-BPDU-GUARD-MIB.mib
-- Revision 1.2  2016/06/28 

ZYXEL-BPDU-GUARD-MIB DEFINITIONS ::= BEGIN

    IMPORTS
	OBJECT-TYPE
		FROM SNMPv2-SMI			-- RFC2578	
	MODULE-IDENTITY
		FROM SNMPv2-SMI
	EnabledStatus
		FROM  P-BRIDGE-MIB
	dot1dBasePort
       	FROM BRIDGE-MIB
	esMgmt			
		FROM ZYXEL-ES-SMI;

	zyxelBpduGuard MODULE-IDENTITY
		LAST-UPDATED	"201410230000Z"    
		ORGANIZATION "Enterprise Solution ZyXEL"     
		CONTACT-INFO
			""	   
		DESCRIPTION
			"The subtree for bpdu guard"
		::= { esMgmt 104 }	

	zyxelBpduGuardSetup	     		OBJECT IDENTIFIER ::= { zyxelBpduGuard 1 }
	zyxelBpduGuardStatus	     	OBJECT IDENTIFIER ::= { zyxelBpduGuard 2 }                    
        
        zyBpduGuardState OBJECT-TYPE
        SYNTAX  EnabledStatus
        MAX-ACCESS  read-write
        STATUS  current
        DESCRIPTION
			"Enable/Disable BPDU guard on the switch."
        ::= { zyxelBpduGuardSetup 1 }
                                               
-- 		zyxelBpduGuardPortTable

		zyxelBpduGuardPortTable OBJECT-TYPE
		SYNTAX	SEQUENCE OF ZyxelBpduGuardPortEntry
        MAX-ACCESS  not-accessible
        STATUS  current
        DESCRIPTION
        	"The table contains BPDU guard port configuration. "
        ::= { zyxelBpduGuardSetup 2 }
        
		zyxelBpduGuardPortEntry OBJECT-TYPE
        SYNTAX	ZyxelBpduGuardPortEntry
        MAX-ACCESS	not-accessible
        STATUS	current
        DESCRIPTION
           	"An entry contains BPDU guard port configuration."
        INDEX          	{ dot1dBasePort }
        ::= { zyxelBpduGuardPortTable 1 }

		ZyxelBpduGuardPortEntry ::=
		SEQUENCE {
			zyBpduGuardPortState	EnabledStatus
		}

        zyBpduGuardPortState OBJECT-TYPE
        SYNTAX  EnabledStatus
        MAX-ACCESS  read-write
        STATUS  current
        DESCRIPTION
        	"Enable/Disable BPDU guard on the port."
        ::= { zyxelBpduGuardPortEntry 1 }  

-- 		zyxelBpduGuardPortInfoTable  
      
        zyxelBpduGuardPortInfoTable OBJECT-TYPE
		SYNTAX	SEQUENCE OF ZyxelBpduGuardPortInfoEntry
        MAX-ACCESS  not-accessible
        STATUS  current
        DESCRIPTION
        	"The table contains BPDU guard port status. "
        ::= { zyxelBpduGuardStatus 1 }
        
		zyxelBpduGuardPortInfoEntry OBJECT-TYPE
        SYNTAX	ZyxelBpduGuardPortInfoEntry
        MAX-ACCESS	not-accessible
        STATUS	current
        DESCRIPTION
           	"An entry contains BPDU guard port status."
        INDEX          	{ dot1dBasePort }
        ::= { zyxelBpduGuardPortInfoTable 1 }

		ZyxelBpduGuardPortInfoEntry ::=
		SEQUENCE {
			zyBpduGuardPortInfoStatus	INTEGER
		}

        zyBpduGuardPortInfoStatus OBJECT-TYPE
        SYNTAX  INTEGER {
        	forwarding(1),    
        	err-disable(2)
        }
        MAX-ACCESS  read-only
        STATUS  current
        DESCRIPTION
        	"BPDU guard status on the port."
        ::= { zyxelBpduGuardPortInfoEntry 1 }  

END
