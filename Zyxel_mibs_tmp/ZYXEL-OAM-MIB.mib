-- ZyXEL Communications Corporation
-- Private Enterprise MIB definition 
  
-- This file describes the ZyXEL Communications Corporation Enterprise MIB.
-- It contains ZyXEL products OIDs, and common managed objects.

-- ZYXEL-OAM-MIB.mib
-- Revision 1.4  2013/12/06 

ZYXEL-OAM-MIB DEFINITIONS ::= BEGIN

    IMPORTS
	OBJECT-TYPE
		FROM SNMPv2-SMI			-- RFC2578	
		
	MODULE-IDENTITY
		FROM SNMPv2-SMI
	
	EnabledStatus
		FROM  P-BRIDGE-MIB

    ifIndex
    	FROM IF-MIB					-- RFC2863

	esMgmt			
		FROM ZYXEL-ES-SMI;

	zyxelOam MODULE-IDENTITY
		LAST-UPDATED	"201207010000Z"    
		ORGANIZATION "Enterprise Solution ZyXEL"     
		CONTACT-INFO
			""	   
		DESCRIPTION
			"The subtree for Operations, Administration, and Maintenance (OAM)"
		::= { esMgmt 56 }

	zyxelOamSetup     		OBJECT IDENTIFIER ::= { zyxelOam 1 }
	

--  118.zyxelOamSetup
	
                               
        zyOamState OBJECT-TYPE
        SYNTAX  EnabledStatus
        MAX-ACCESS  read-write
        STATUS  current
        DESCRIPTION
 			"Enable/Disable administrative status on the switch."
        ::= { zyxelOamSetup 1 }


-- 		zyxelOamPortTable

        zyxelOamPortTable OBJECT-TYPE
        SYNTAX	SEQUENCE OF ZyxelOamPortEntry
        MAX-ACCESS  not-accessible
        STATUS  current
        DESCRIPTION
			"The table contains OAM (Operations, Administration, and Maintenance) port configuration. "
        ::= { zyxelOamSetup 2 }
        
		zyxelOamPortEntry OBJECT-TYPE
        SYNTAX	ZyxelOamPortEntry
        MAX-ACCESS	not-accessible
        STATUS	current
        DESCRIPTION    	
        	"An entry contains OAM port configuration."
        INDEX          	{ ifIndex }
        ::= { zyxelOamPortTable 1 }

        ZyxelOamPortEntry ::=
           SEQUENCE {
	       zyOamPortFunctionsSupported          BITS
           }

        zyOamPortFunctionsSupported OBJECT-TYPE
        SYNTAX      BITS {
                      unidirectionalSupport (0),
                      loopbackSupport(1),
                      eventSupport(2),
                      variableSupport(3)
                    }
        MAX-ACCESS  read-write
        STATUS	current
        DESCRIPTION
          "The OAM functions supported on this Ethernet-like interface. OAM consists of separate functional sets beyond 
          the basic discovery process that is always required.  These functional groups can be supported independently by 
          any implementation. These values are communicated to the peer via the local configuration field of Information 
          OAMPDUs.
			Setting 'unidirectionalSupport(0)' indicates that the OA entity supports the transmission of OAMPDUs on links 
			that are operating in unidirectional mode (traffic flowing in one direction only).  
			Setting 'loopbackSupport(1)' indicates that the OAM entity can initiate and respond to loopback commands. 
			Setting 'eventSupport(2)' indicates that the OAM entity can send and receive Event Notification OAMPDUs.  
			Setting 'variableSupport(3)' indicates that the OAM entity can send and receive Variable Request and Response 
			OAMPDUs.
          "
        REFERENCE   "[802.3ah], 30.3.6.1.6"
        ::= { zyxelOamPortEntry 1 }

END
