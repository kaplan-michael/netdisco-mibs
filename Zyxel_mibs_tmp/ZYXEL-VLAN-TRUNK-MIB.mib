-- ZyXEL Communications Corporation
-- Private Enterprise MIB definition 
  
-- This file describes the ZyXEL Communications Corporation Enterprise MIB.
-- It contains ZyXEL products OIDs, and common managed objects.

-- ZYXEL-VLAN-TRUNK-MIB.mib
-- Revision 1.4  2013/12/06 

ZYXEL-VLAN-TRUNK-MIB DEFINITIONS ::= BEGIN

    IMPORTS

	OBJECT-TYPE
		FROM SNMPv2-SMI			-- RFC2578	

	MODULE-IDENTITY
    FROM SNMPv2-SMI
    
	EnabledStatus
		FROM  P-BRIDGE-MIB
	
	dot1dBasePort
       	FROM BRIDGE-MIB
	esMgmt			
		FROM ZYXEL-ES-SMI;

	zyxelVlanTrunk MODULE-IDENTITY
		LAST-UPDATED	"201207010000Z"    
		ORGANIZATION "Enterprise Solution ZyXEL"     
		CONTACT-INFO
			""	   
		DESCRIPTION
			"The subtree for VLAN trunk"
		::= { esMgmt 90 }	

	zyxelVlanTrunkSetup 			OBJECT IDENTIFIER ::= { zyxelVlanTrunk 1 }
		
-- *******************************************************************
-- *
-- * zyxelVlanTrunkSetup
-- *
-- *******************************************************************  

-- zyxelVlanTrunkPortTable
        zyxelVlanTrunkPortTable OBJECT-TYPE
        SYNTAX	SEQUENCE OF ZyxelVlanTrunkPortEntry
        MAX-ACCESS  not-accessible
        STATUS  current
        DESCRIPTION
                 	"This table that controls VLAN trunking on individual ports."
        ::= { zyxelVlanTrunkSetup 1 }
        
		zyxelVlanTrunkPortEntry OBJECT-TYPE
        SYNTAX	ZyxelVlanTrunkPortEntry
        MAX-ACCESS	not-accessible
        STATUS	current
        DESCRIPTION    	"VLAN trunk configuration for a particular port. 
        				This configuration parameter controls the VLAN trunking on those port in this table."
        INDEX          	{ dot1dBasePort }
        ::= { zyxelVlanTrunkPortTable 1 }

        ZyxelVlanTrunkPortEntry ::=
           SEQUENCE {
        	zyVlanTrunkPortState		EnabledStatus
           }

        zyVlanTrunkPortState OBJECT-TYPE
        SYNTAX  EnabledStatus
        MAX-ACCESS  read-write
        STATUS  current
        DESCRIPTION
                      	"Enable/Disable VlanTrunking on the indicated port. Enable(1) to allow frames belonging 
                      	to unknown VLAN groups to pass through the switch."
        ::= { zyxelVlanTrunkPortEntry 1 }
    
END
