-- ZyXEL Communications Corporation
-- Private Enterprise MIB definition 
  
-- This file describes the ZyXEL Communications Corporation Enterprise MIB.
-- It contains ZyXEL products OIDs, and common managed objects.

-- ZYXEL-TRTCM-MIB.mib
-- Revision 1.6  2013/12/06 

ZYXEL-TRTCM-MIB DEFINITIONS ::= BEGIN

    IMPORTS
    
	OBJECT-TYPE
		FROM SNMPv2-SMI			-- RFC2578	
		
	MODULE-IDENTITY
		FROM SNMPv2-SMI
		
	RowStatus
		FROM SNMPv2-TC			-- RFC2579
		
	DisplayString                                          
	  	FROM SNMPv2-TC			-- RFC2579
	  	
	EnabledStatus
		FROM  P-BRIDGE-MIB

	dot1dBasePort
     FROM BRIDGE-MIB

	esMgmt			
		FROM ZYXEL-ES-SMI;

	zyxelTrtcm MODULE-IDENTITY
		LAST-UPDATED	"201207010000Z"    
		ORGANIZATION "Enterprise Solution ZyXEL"     
		CONTACT-INFO
			""	   
		DESCRIPTION
			"The subtree for Two Rate Three Color Marker (trTCM)"
		::= { esMgmt 85 }	

	zyxelTrtcmSetup 				OBJECT IDENTIFIER ::= { zyxelTrtcm 1 }
	
-- *******************************************************************
-- *
-- * zyxelTrtcmSetup
-- *
-- ******************************************************************* 

-- zyxelTctcmState	
        zyTctcmState OBJECT-TYPE
        SYNTAX  EnabledStatus
        MAX-ACCESS  read-write
        STATUS  current
        DESCRIPTION
                      	"Enable/Disable TRTCM (Two-rate three color marker) on the switch. The switch evaluates and marks the packets based on the TRTCM settings.
						Note: You must also enable DiffServ on the switch and the individual ports for the switch to drop red (high loss priority) colored packets."
        ::= { zyxelTrtcmSetup 1 }  

-- zyxelTrtcmMode
        zyTrtcmMode OBJECT-TYPE
        SYNTAX  INTEGER {
        	colorAware(0),
        	colorBlind(1)
        	}
        MAX-ACCESS  read-write
        STATUS  current
        DESCRIPTION
                      	"Enter colorBlind to have the switch treat all incoming packets as uncolored. 
                      	All incoming packets are evaluated against the CIR and PIR. Enter colorAware to treat the 
                      	packets as marked by some preceding entity. Incoming packets are evaluated based on their 
                      	existing color. Incoming packets that are not marked proceed through the switch."
        ::= { zyxelTrtcmSetup 2 } 

-- zyxelTrtcmPortTable       
        zyxelTrtcmPortTable OBJECT-TYPE
        SYNTAX	SEQUENCE OF ZyxelTrtcmPortEntry
        MAX-ACCESS  not-accessible
        STATUS  current
        DESCRIPTION
                 	"The table contains TRTCM port configuration."
        ::= { zyxelTrtcmSetup 3 }
        
		zyxelTrtcmPortEntry OBJECT-TYPE
        SYNTAX	ZyxelTrtcmPortEntry
        MAX-ACCESS	not-accessible
        STATUS	current
        DESCRIPTION    	"An entry contains TRTCM port configuration."
        INDEX          	{ dot1dBasePort }
        ::= { zyxelTrtcmPortTable 1 }

        ZyxelTrtcmPortEntry ::=
		SEQUENCE {
	       	zyTrtcmPortState		EnabledStatus,
			zyTrtcmPortCir			INTEGER,     
			zyTrtcmPortPir			INTEGER,  
			zyTrtcmPortDscpProfile	DisplayString
		}

        zyTrtcmPortState OBJECT-TYPE
        SYNTAX  EnabledStatus
        MAX-ACCESS  read-create
        STATUS  current
        DESCRIPTION
                      	"Enable/Disable TRTCM on the port."
        ::= { zyxelTrtcmPortEntry 1 }
        
        zyTrtcmPortCir OBJECT-TYPE
        SYNTAX  INTEGER
        MAX-ACCESS  read-write
        STATUS  current
        DESCRIPTION
                      	"Specify the Commit Information Rate (CIR) for this port."
        ::= { zyxelTrtcmPortEntry 2 }
        
        zyTrtcmPortPir OBJECT-TYPE
        SYNTAX  INTEGER
        MAX-ACCESS  read-write
        STATUS  current
        DESCRIPTION
                      	"Specify the Peak Information Rate (PIR) for this port."
        ::= { zyxelTrtcmPortEntry 3 }
        
        zyTrtcmPortDscpProfile OBJECT-TYPE
        SYNTAX  DisplayString
        MAX-ACCESS  read-write
        STATUS  current
        DESCRIPTION
                      	"The name of trtcm dscp profile with specifed CIR and PIR setting on the port."
        ::= { zyxelTrtcmPortEntry 4 }    
        
-- zyxelTrtcmMaxNumberOfDscpProfiles
		zyTrtcmMaxNumberOfDscpProfiles OBJECT-TYPE
        SYNTAX  INTEGER
        MAX-ACCESS  read-only
        STATUS  current
        DESCRIPTION
                      	"The maximum number of TRTCM DSCP profile that can be created."
        ::= { zyxelTrtcmSetup 4 }  
        
-- zyxelTrtcmDscpProfileTable       
        zyxelTrtcmDscpProfileTable OBJECT-TYPE
        SYNTAX	SEQUENCE OF ZyxelTrtcmDscpProfileEntry
        MAX-ACCESS  not-accessible
        STATUS  current
        DESCRIPTION
                 	"AThe talbe contains TRTCM profile configuration."
        ::= { zyxelTrtcmSetup 5}
        
		zyxelTrtcmDscpProfileEntry OBJECT-TYPE
        SYNTAX	ZyxelTrtcmDscpProfileEntry
        MAX-ACCESS	not-accessible
        STATUS	current
        DESCRIPTION    	"An entry contains TRTCM profile configuration."
        INDEX          	{ zyTrtcmDscpProfileName }
        ::= { zyxelTrtcmDscpProfileTable 1 }

        ZyxelTrtcmDscpProfileEntry ::=
		SEQUENCE {
	       	zyTrtcmDscpProfileName			DisplayString,
			zyTrtcmDscpProfileDscpGreen		INTEGER,     
			zyTrtcmDscpProfileDscpYellow	INTEGER,  
			zyTrtcmDscpProfileDscpRed		INTEGER,
			zyTrtcmDscpProfileRowstatus		RowStatus
		}

        zyTrtcmDscpProfileName OBJECT-TYPE
        SYNTAX  DisplayString
        MAX-ACCESS  read-only
        STATUS  current
        DESCRIPTION
                      	"The name of TRTCM DSCP profile."
        ::= { zyxelTrtcmDscpProfileEntry 1 }
        
        zyTrtcmDscpProfileDscpGreen OBJECT-TYPE
        SYNTAX  INTEGER
        MAX-ACCESS  read-write
        STATUS  current
        DESCRIPTION
                      	"Specify the DSCP Green value to use for packets with low packet loss priority."
        ::= { zyxelTrtcmDscpProfileEntry 2 }
        
        zyTrtcmDscpProfileDscpYellow OBJECT-TYPE
        SYNTAX  INTEGER
        MAX-ACCESS  read-write
        STATUS  current
        DESCRIPTION
                      	"Specify the DSCP Yellow value to use for packets with medium packet loss priority. "
        ::= { zyxelTrtcmDscpProfileEntry 3 }
        
        zyTrtcmDscpProfileDscpRed OBJECT-TYPE
        SYNTAX  INTEGER
        MAX-ACCESS  read-write
        STATUS  current
        DESCRIPTION
                      	"Specify the DSCP red value to use for packets with high packet loss priority."
        ::= { zyxelTrtcmDscpProfileEntry 4 }   
        
        zyTrtcmDscpProfileRowstatus OBJECT-TYPE
        SYNTAX  RowStatus
        MAX-ACCESS  read-create
        STATUS  current
        DESCRIPTION
                      	"This object allows to create and delete a TRTCM DSCP profile entry."
        ::= { zyxelTrtcmDscpProfileEntry 5 }    
 
       
 END
