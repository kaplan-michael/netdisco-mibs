-- ZyXEL Communications Corporation
-- Private Enterprise MIB definition 
  
-- This file describes the ZyXEL Communications Corporation Enterprise MIB.
-- It contains ZyXEL products OIDs, and common managed objects.

-- ZYXEL-CPU-PROTECTION-MIB.mib
-- Revision 1.4  2013/12/06 

ZYXEL-CPU-PROTECTION-MIB DEFINITIONS ::= BEGIN

    IMPORTS
	OBJECT-TYPE
		FROM SNMPv2-SMI			-- RFC2578	
		
	MODULE-IDENTITY
		FROM SNMPv2-SMI
	
	esMgmt			
		FROM ZYXEL-ES-SMI;

	zyxelCpuProtection MODULE-IDENTITY
		LAST-UPDATED	"201207010000Z"    
		ORGANIZATION "Enterprise Solution ZyXEL"     
		CONTACT-INFO
			""	   
		DESCRIPTION
			"The subtree for cpu protection"
		::= { esMgmt 16 }	

	zyxelCpuProtectionSetup 		OBJECT IDENTIFIER ::= { zyxelCpuProtection 1 }		

-- ******************************************************************
-- *
-- 16. zyxelCpuProtection
-- *
-- ****************************************************************** 

     	zyxelCpuProtectionTable	OBJECT-TYPE
        SYNTAX	SEQUENCE OF ZyxelCpuProtectionEntry
        MAX-ACCESS  not-accessible
        STATUS  current
        DESCRIPTION
        "The table contains CPU protection configuration."
        ::= { zyxelCpuProtectionSetup 1 }   
        
		zyxelCpuProtectionEntry OBJECT-TYPE
        SYNTAX	ZyxelCpuProtectionEntry
        MAX-ACCESS	not-accessible
        STATUS	current
        DESCRIPTION    	
		"An entry contains CPU protection configuration."
        INDEX          	{ zyCpuProtectionPort, zyCpuProtectionReasonType}
        ::= { zyxelCpuProtectionTable 1 }

        ZyxelCpuProtectionEntry ::=
		SEQUENCE {
        	zyCpuProtectionPort       	INTEGER,
        	zyCpuProtectionReasonType	INTEGER,
        	zyCpuProtectionRateLimit 	INTEGER
          }
                
        zyCpuProtectionPort OBJECT-TYPE
        SYNTAX  INTEGER           
        MAX-ACCESS  not-accessible
        STATUS  current
        DESCRIPTION
        "This field displays the port number."
        ::= { zyxelCpuProtectionEntry 1 }      
        
        
        zyCpuProtectionReasonType OBJECT-TYPE
        SYNTAX  INTEGER{
	        arp(1),
	        bpdu(2),
		    igmp(3)
        }
        MAX-ACCESS  not-accessible
        STATUS  current
        DESCRIPTION
        "This field displays which type of control packets on the specified port."
        ::= { zyxelCpuProtectionEntry 2}    
        

        zyCpuProtectionRateLimit OBJECT-TYPE
        SYNTAX  INTEGER(0..256)
        MAX-ACCESS  read-write
        STATUS  current
        DESCRIPTION
        "Enter a number from 0 to 256 to specified how many control packets this port can receive or transmit per second. 
		 0 means no rate limit."
        ::= { zyxelCpuProtectionEntry 3}    
        
                          
END
