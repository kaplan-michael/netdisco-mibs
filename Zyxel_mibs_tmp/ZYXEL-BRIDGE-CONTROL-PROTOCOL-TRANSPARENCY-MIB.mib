-- ZyXEL Communications Corporation
-- Private Enterprise MIB definition 
  
-- This file describes the ZyXEL Communications Corporation Enterprise MIB.
-- It contains ZyXEL products OIDs, and common managed objects.

-- ZYXEL-BRIDGE-CONTROL-PROTOCOL-TRANSPARENCY-MIB.mib
-- Revision 1.4  2013/12/06 

ZYXEL-BRIDGE-CONTROL-PROTOCOL-TRANSPARENCY-MIB DEFINITIONS ::= BEGIN
    IMPORTS
	OBJECT-TYPE
		FROM SNMPv2-SMI			-- RFC2578	
		
	MODULE-IDENTITY
		FROM SNMPv2-SMI
	
	EnabledStatus
		FROM  P-BRIDGE-MIB

	dot1dBasePort
		FROM BRIDGE-MIB

	esMgmt			
		FROM ZYXEL-ES-SMI;

	zyxelBridgeControlProtocolTransparency MODULE-IDENTITY
		LAST-UPDATED	"201207010000Z"    
		ORGANIZATION "Enterprise Solution ZyXEL"     
		CONTACT-INFO
			""	   
		DESCRIPTION
			"The subtree for bridge control protocol transparency"
		::= { esMgmt 15 }	

	zyxelBridgeControlProtocolTransparencySetup 	OBJECT IDENTIFIER ::= { zyxelBridgeControlProtocolTransparency 1 }
	
    
--  1.zyxelBridgeControlProtocolTransparencySetup

        zyBridgeControlProtocolTransparencyState OBJECT-TYPE
        SYNTAX  EnabledStatus
        MAX-ACCESS  read-write
        STATUS  current
        DESCRIPTION
        "Enable/Disable bridge control protocol transparency on the switch."
        ::= { zyxelBridgeControlProtocolTransparencySetup 1 }

-- 		zyxelBridgeControlProtocolTransparencyPortTable

        zyxelBridgeControlProtocolTransparencyPortTable OBJECT-TYPE
        SYNTAX	SEQUENCE OF ZyxelBridgeControlProtocolTransparencyPortEntry
        MAX-ACCESS  not-accessible
        STATUS  current
        DESCRIPTION
        "The table contains bridge control protocol transparency port configuration."
        ::= { zyxelBridgeControlProtocolTransparencySetup 2 }
        
		zyxelBridgeControlProtocolTransparencyPortEntry OBJECT-TYPE
        SYNTAX	ZyxelBridgeControlProtocolTransparencyPortEntry
        MAX-ACCESS	not-accessible
        STATUS	current
        DESCRIPTION    	
		"An entry contains bridge control protocol transparency port configuration."
        INDEX          	{ dot1dBasePort }
        ::= { zyxelBridgeControlProtocolTransparencyPortTable 1 }

        ZyxelBridgeControlProtocolTransparencyPortEntry ::=
           SEQUENCE {
        	zyBridgeControlProtocolTransparencyPortMode	INTEGER
           }

        zyBridgeControlProtocolTransparencyPortMode OBJECT-TYPE
        SYNTAX  INTEGER{
		peer(0),
		tunnel(1),
		discard(2),
		network(3)
        }
        MAX-ACCESS  read-write
        STATUS  current
        DESCRIPTION
        "Configure bridge control protocol transparency mode for the port. 
		 'Peer' means to process any BPDU (Bridge Protocol Data Unit) received on this port. 
		 'Tunnel' means to forward BPDUs received on this port. 
		 'Discard' means to drop any BPDU received on this port. 
		 'Network' means to process a BPDU with no VLAN tag and forward a tagged BPDU."
        ::= { zyxelBridgeControlProtocolTransparencyPortEntry 1 }

END
