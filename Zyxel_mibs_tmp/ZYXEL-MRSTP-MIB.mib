-- ZyXEL Communications Corporation
-- Private Enterprise MIB definition 
  
-- This file describes the ZyXEL Communications Corporation Enterprise MIB.
-- It contains ZyXEL products OIDs, and common managed objects.

-- ZYXEL-MRSTP-MIB.mib
-- Revision 1.4  2013/12/06 

ZYXEL-MRSTP-MIB DEFINITIONS ::= BEGIN

    IMPORTS
	OBJECT-TYPE
		FROM SNMPv2-SMI			-- RFC2578	
		
	MODULE-IDENTITY
		FROM SNMPv2-SMI
	
	EnabledStatus
		FROM  P-BRIDGE-MIB
		
	dot1dBasePort
       	FROM BRIDGE-MIB

    BridgeId, Timeout
        FROM BRIDGE-MIB  
       

    NOTIFICATION-TYPE
        FROM SNMPv2-SMI

	 TimeTicks
        FROM SNMPv2-SMI
  
   Counter32
  	FROM SNMPv2-SMI

 	esMgmt			
		FROM ZYXEL-ES-SMI;

	zyxelMrstp MODULE-IDENTITY
		LAST-UPDATED	"201207010000Z"    
		ORGANIZATION "Enterprise Solution ZyXEL"     
		CONTACT-INFO
			""	   
		DESCRIPTION
			"The subtree for Multiple Rapid Spanning Tree Protocol (MRSTP)"
		::= { esMgmt 52 }

	zyxelMrstpSetup	     	OBJECT IDENTIFIER ::= { zyxelMrstp 1 }
	zyxelMrstpStatus     	OBJECT IDENTIFIER ::= { zyxelMrstp 2 }
	zyxelMrstpNotifications	OBJECT IDENTIFIER ::= { zyxelMrstp 3 }

                       
       		                 
		zyxelMrstpBridgeTable  OBJECT-TYPE
		SYNTAX	SEQUENCE OF ZyxelMrstpBridgeEntry 
		MAX-ACCESS  not-accessible
		STATUS  current
		DESCRIPTION
			"The table contains MRSTP bridge configuration."
	    ::= { zyxelMrstpSetup 1 }	

		zyxelMrstpBridgeEntry  OBJECT-TYPE
        SYNTAX	ZyxelMrstpBridgeEntry 
        MAX-ACCESS	not-accessible
        STATUS	current
        DESCRIPTION    	
        	"An entry contains MRSTP bridge configuration."
        INDEX          	{ zyMrstpBridgeIndex }
        ::= { zyxelMrstpBridgeTable 1 }

        ZyxelMrstpBridgeEntry ::=
			SEQUENCE {
	           	zyMrstpBridgeIndex						INTEGER,
	           	zyMrstpBridgeState						EnabledStatus,  	
	           	zyMrstpBridgePriority					INTEGER,
	        	zyMrstpBridgeRootMaxAge					Timeout,
	        	zyMrstpBridgeRootHelloTime				Timeout,
	        	zyMrstpBridgeRootForwardDelay			Timeout
			}
         
          zyMrstpBridgeIndex OBJECT-TYPE
              SYNTAX  INTEGER
              MAX-ACCESS  not-accessible
              STATUS  current
              DESCRIPTION
				"The tree index of the MRSTP."
              ::= { zyxelMrstpBridgeEntry 1 }
			
		  zyMrstpBridgeState OBJECT-TYPE
        	SYNTAX  EnabledStatus
        	MAX-ACCESS  read-write
        	STATUS  current
        	DESCRIPTION
				"Enable/Disable on the mrstp bridge."
        	::= { zyxelMrstpBridgeEntry 2 }
                
          zyMrstpBridgePriority OBJECT-TYPE
              SYNTAX  INTEGER (0..65535)
              MAX-ACCESS  read-write
              STATUS  current
              DESCRIPTION
                      "The value of the write-able portion of the Bridge
                      ID, i.e., the first two octets of the (8 octet
                      long) Bridge ID.  The other (last) 6 octets of the
                      Bridge ID are given by the value of
                      dot1dBaseBridgeAddress."
              REFERENCE
                      "IEEE 802.1D-1990: Section 4.5.3.7"
              ::= { zyxelMrstpBridgeEntry 3 }

          zyMrstpBridgeRootMaxAge OBJECT-TYPE
              SYNTAX  Timeout (600..4000)
              MAX-ACCESS  read-write
              STATUS  current
              DESCRIPTION
                      "The value that all bridges use for MaxAge when this bridge is acting as the root.  
                      Note that 802.1D-1990 specifies that the range for this parameter is related to the 
                      value of zyxelMrstpBridgeHelloTime. The granularity of this  timer is specified by 
                      802.1D-1990 to be 1 second. An agent may return a badValue error if a set is  attempted 
                      to a value which is not a whole number of seconds."
              REFERENCE
                      "IEEE 802.1D-1990: Section 4.5.3.8"
              ::= { zyxelMrstpBridgeEntry 4 }

          zyMrstpBridgeRootHelloTime OBJECT-TYPE
              SYNTAX  Timeout (100..1000)
              MAX-ACCESS  read-write
              STATUS  current
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { zyxelMrstpBridgeEntry 5 }

          zyMrstpBridgeRootForwardDelay OBJECT-TYPE
              SYNTAX  Timeout (400..3000)
              MAX-ACCESS  read-write
              STATUS  current
              DESCRIPTION
                      "The value that all bridges use for ForwardDelay
                      when this bridge is acting as the root.  Note that
                      802.1D-1990 specifies that the range for this
                      parameter is related to the value of
                      mrstpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { zyxelMrstpBridgeEntry 6 }

--		zyxelMrstpPortTable

          zyxelMrstpPortTable OBJECT-TYPE
              SYNTAX  SEQUENCE OF ZyxelMrstpPortEntry
              MAX-ACCESS  not-accessible
              STATUS  current
              DESCRIPTION
                      "The table contains MRSTP port configuration."
              ::= { zyxelMrstpSetup 2 }

          zyxelMrstpPortEntry OBJECT-TYPE
              SYNTAX  ZyxelMrstpPortEntry
              MAX-ACCESS  not-accessible
              STATUS  current
              DESCRIPTION
                      "An entry contains MRSTP port configuration."
              INDEX   { dot1dBasePort }
              ::= { zyxelMrstpPortTable 1 }

          ZyxelMrstpPortEntry ::=
              SEQUENCE {
                  zyMrstpPortPriority 			INTEGER,
                  zyMrstpPortEnable				EnabledStatus,
                  zyMrstpPortPathCost			INTEGER,
                  zyMrstpPortOnBridgeIndex		INTEGER,
                  zyMrstpPortAdminEdgePort		INTEGER
              }

          zyMrstpPortPriority OBJECT-TYPE
              SYNTAX  INTEGER (0..255)
              MAX-ACCESS  read-write
              STATUS  current
              DESCRIPTION
                      "The value of the priority field which is
                      contained in the first (in network byte order)
                      octet of the (2 octet long) Port ID.  The other
                      octet of the Port ID is given by the value of
                      mrstpPort."
              REFERENCE
                      "IEEE 802.1D-1990: Section 4.5.5.1"
              ::= { zyxelMrstpPortEntry 1 }

          zyMrstpPortEnable OBJECT-TYPE
              SYNTAX  EnabledStatus 
              MAX-ACCESS  read-write
              STATUS  current
              DESCRIPTION
                      "Enable/Disable the MRSTP on the port."
              REFERENCE
                      "IEEE 802.1D-1990: Section 4.5.5.2"
              ::= { zyxelMrstpPortEntry 2 }

          zyMrstpPortPathCost OBJECT-TYPE
              SYNTAX  INTEGER (1..200000000)
              MAX-ACCESS  read-write
              STATUS  current
              DESCRIPTION
                      "The contribution of this port to the path cost of paths towards the spanning tree root 
                      which include this port.  802.1D-2004 recommends that the default value of this parameter 
                      be in inverse proportion to the speed of the attached LAN."
              REFERENCE
                      "IEEE 802.1D-1990: Section 4.5.5.3"
              ::= { zyxelMrstpPortEntry 3 }

          zyMrstpPortOnBridgeIndex OBJECT-TYPE
              SYNTAX  INTEGER
              MAX-ACCESS  read-write
              STATUS  current
              DESCRIPTION
                      "Indetify the bridge index that this port joined to in MRSTP."
              ::= { zyxelMrstpPortEntry 4 }
              
          zyMrstpPortAdminEdgePort OBJECT-TYPE
              SYNTAX  INTEGER {
                          true(1),
                          false(2)
                      }
              MAX-ACCESS  read-write
              STATUS  current
              DESCRIPTION
                      "The administrative value of the Edge Port parameter.
                      A value of true(1) indicates that this port should be assumed as an edge-port, 
                      and a value of false(2) indicates that this port should be assumed as a non-edge-port."
              REFERENCE
                      "IEEE 802.1t clause 14.8.2, 18.3.3"
              ::= { zyxelMrstpPortEntry 5 }
              
              
 
--Mrstp Statup                       
       		                 
		zyxelMrstpBridgeInfoTable  OBJECT-TYPE
		SYNTAX	SEQUENCE OF ZyxelMrstpBridgeInfoEntry 
		MAX-ACCESS  not-accessible
		STATUS  current
		DESCRIPTION
			"The table contains MRSTP bridge information."
	    ::= { zyxelMrstpStatus 1 }	

		zyxelMrstpBridgeInfoEntry  OBJECT-TYPE
        SYNTAX	ZyxelMrstpBridgeInfoEntry 
        MAX-ACCESS	not-accessible
        STATUS	current
        DESCRIPTION    	
        	"An entry contains MRSTP bridge information."
        INDEX          	{ zyMrstpBridgeInfoIndex }
        ::= { zyxelMrstpBridgeInfoTable 1 }

        ZyxelMrstpBridgeInfoEntry ::=
			SEQUENCE {
	           	zyMrstpBridgeInfoIndex						INTEGER,
	           	zyMrstpBridgeInfoProtocolSpecification		INTEGER,      	
	           	zyMrstpBridgeInfoTimeSinceTopologyChange	TimeTicks,
	        	zyMrstpBridgeInfoTopologyChanges			Counter32,
	        	zyMrstpBridgeInfoDesignatedRoot				BridgeId,
	        	zyMrstpBridgeInfoRootCost					INTEGER,
	        	zyMrstpBridgeInfoRootPort					INTEGER,
	        	zyMrstpBridgeInfoMaxAge						Timeout,
	        	zyMrstpBridgeInfoHelloTime					Timeout,
	        	zyMrstpBridgeInfoHoldTime					INTEGER,
	        	zyMrstpBridgeInfoForwardDelay				Timeout,
	        	zyMrstpBridgeInfoRootMaxAge					Timeout,
	        	zyMrstpBridgeInfoRootHelloTime				Timeout,
	        	zyMrstpBridgeInfoRootForwardDelay			Timeout
			}     
    
          zyMrstpBridgeInfoIndex OBJECT-TYPE
              SYNTAX  INTEGER
              MAX-ACCESS  not-accessible
              STATUS  current
              DESCRIPTION
				"The tree index of the MRSTP."
              ::= { zyxelMrstpBridgeInfoEntry 1 }
			        
          zyMrstpBridgeInfoProtocolSpecification OBJECT-TYPE
              SYNTAX  INTEGER {
                          unknown(1),
                          decLb100(2),
                          ieee8021d(3)
                      }
              MAX-ACCESS  read-only
              STATUS  current
              DESCRIPTION
					"An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { zyxelMrstpBridgeInfoEntry 2 }
        
          zyMrstpBridgeInfoTimeSinceTopologyChange OBJECT-TYPE
              SYNTAX  TimeTicks
              MAX-ACCESS  read-only
              STATUS  current
              DESCRIPTION
                      "The time (in hundredths of a second) since the
                      last time a topology change was detected by the
                      bridge entity."
              REFERENCE
                      "IEEE 802.1D-1990: Section 6.8.1.1.3"
              ::= { zyxelMrstpBridgeInfoEntry 3 }

          zyMrstpBridgeInfoTopologyChanges OBJECT-TYPE
              SYNTAX  Counter32
              MAX-ACCESS  read-only
              STATUS  current
              DESCRIPTION
                      "The total number of topology changes detected by
                      this bridge since the management entity was last
                      reset or initialized."
              REFERENCE
                      "IEEE 802.1D-1990: Section 6.8.1.1.3"
              ::= { zyxelMrstpBridgeInfoEntry 4 }

          zyMrstpBridgeInfoDesignatedRoot OBJECT-TYPE
              SYNTAX  BridgeId
              MAX-ACCESS  read-only
              STATUS  current
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { zyxelMrstpBridgeInfoEntry 5 }

          zyMrstpBridgeInfoRootCost OBJECT-TYPE
              SYNTAX  INTEGER
              MAX-ACCESS  read-only
              STATUS  current
              DESCRIPTION
                      "The cost of the path to the root as seen from
                      this bridge."
              REFERENCE
                      "IEEE 802.1D-1990: Section 4.5.3.2"
              ::= { zyxelMrstpBridgeInfoEntry 6 }

          zyMrstpBridgeInfoRootPort OBJECT-TYPE
              SYNTAX  INTEGER
              MAX-ACCESS  read-only
              STATUS  current
              DESCRIPTION
                      "The port number of the port which offers the
                      lowest cost path from this bridge to the root
                      bridge."
              REFERENCE
                      "IEEE 802.1D-1990: Section 4.5.3.3"
              ::= { zyxelMrstpBridgeInfoEntry 7 }

          zyMrstpBridgeInfoMaxAge OBJECT-TYPE
              SYNTAX  Timeout
              MAX-ACCESS  read-only
              STATUS  current
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { zyxelMrstpBridgeInfoEntry 8 }

          zyMrstpBridgeInfoHelloTime OBJECT-TYPE
              SYNTAX  Timeout
              MAX-ACCESS  read-only
              STATUS  current
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { zyxelMrstpBridgeInfoEntry 9 }

          zyMrstpBridgeInfoHoldTime OBJECT-TYPE
              SYNTAX  INTEGER
              MAX-ACCESS  read-only
              STATUS  current
              DESCRIPTION
                      "This time value determines the interval length
                      during which no more than two Configuration bridge
                      PDUs shall be transmitted by this node, in units
                      of hundredths of a second."
              REFERENCE
                      "IEEE 802.1D-1990: Section 4.5.3.14"
              ::= { zyxelMrstpBridgeInfoEntry 10 }

          zyMrstpBridgeInfoForwardDelay OBJECT-TYPE
              SYNTAX  Timeout
              MAX-ACCESS  read-only
              STATUS  current
              DESCRIPTION
                      "This time value, measured in units of hundredths of a second, controls how fast a port 
                      changes its spanning state when moving towards the Forwarding  state.  The value determines 
                      how long the port  stays in each of the Listening and Learning  states, which precede 
                      the Forwarding state.  This  value is also used, when a topology change has  been detected 
                      and is underway, to age all dynamic entries in the Forwarding Database.  [Note that this 
                      value is the one that this bridge i currently using, in contrast to 
                      zyxelMrstpBridgeInfoForwardDelay which is the value that  this bridge and all others would 
                      start using  if/when this bridge were to become the root."
              REFERENCE
                      "IEEE 802.1D-1990: Section 4.5.3.6"
              ::= { zyxelMrstpBridgeInfoEntry 11 }

          zyMrstpBridgeInfoRootMaxAge OBJECT-TYPE
              SYNTAX  Timeout (600..4000)
              MAX-ACCESS  read-write
              STATUS  current
              DESCRIPTION
                      "The value that all bridges use for MaxAge when this bridge is acting as the root.  Note 
                      that 802.1D-1990 specifies that the range for this parameter is related to the value of 
                      zyxelMrstpBridgeInfoHelloTime. The granularity of this  timer is specified by 802.1D-1990 
                      to be 1 second. An agent may return a badValue error if a set is  attempted to a value 
                      which is not a whole number of seconds."
              REFERENCE
                      "IEEE 802.1D-1990: Section 4.5.3.8"
              ::= { zyxelMrstpBridgeInfoEntry 12 }

          zyMrstpBridgeInfoRootHelloTime OBJECT-TYPE
              SYNTAX  Timeout (100..1000)
              MAX-ACCESS  read-write
              STATUS  current
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { zyxelMrstpBridgeInfoEntry 13 }

          zyMrstpBridgeInfoRootForwardDelay OBJECT-TYPE
              SYNTAX  Timeout (400..3000)
              MAX-ACCESS  read-write
              STATUS  current
              DESCRIPTION
                      "The value that all bridges use for ForwardDelay
                      when this bridge is acting as the root.  Note that
                      802.1D-1990 specifies that the range for this
                      parameter is related to the value of
                      MrstpBridgeInfoMaxAge.  The granularity of this
                      timer is specified by 802.1D-1990 to be 1 second.
                      An agent may return a badValue error if a set is
                      attempted to a value which is not a whole number
                      of seconds."
              REFERENCE
                      "IEEE 802.1D-1990: Section 4.5.3.10"
              ::= { zyxelMrstpBridgeInfoEntry 14 }

--		zyxelMrstpPortInfoTable

          zyxelMrstpPortInfoTable OBJECT-TYPE
              SYNTAX  SEQUENCE OF ZyxelMrstpPortInfoEntry
              MAX-ACCESS  not-accessible
              STATUS  current
              DESCRIPTION
                      "The table contains MRSTP port information."
              ::= { zyxelMrstpStatus 2 }

          zyxelMrstpPortInfoEntry OBJECT-TYPE
              SYNTAX  ZyxelMrstpPortInfoEntry
              MAX-ACCESS  not-accessible
              STATUS  current
              DESCRIPTION
                      "An entry contains MRSTP port information."
              INDEX   { dot1dBasePort }
              ::= { zyxelMrstpPortInfoTable 1 }

          ZyxelMrstpPortInfoEntry ::=
              SEQUENCE {
                  zyMrstpPortInfoState 				INTEGER,
                  zyMrstpPortInfoDesignatedRoot		BridgeId,
                  zyMrstpPortInfoDesignatedCost		INTEGER,
                  zyMrstpPortInfoDesignatedBridge	BridgeId,
                  zyMrstpPortInfoDesignatedPort		OCTET STRING,
                  zyMrstpPortInfoForwardTransitions	Counter32,
          		  zyMrstpPortInfoOperEdgePort		INTEGER
              }

          zyMrstpPortInfoState OBJECT-TYPE
              SYNTAX  INTEGER {
                          disabled(1),
                          blocking(2),
                          listening(3),
                          learning(4),
                          forwarding(5),
                          broken(6)
                      }
              MAX-ACCESS  read-only
              STATUS  current
              DESCRIPTION
                      "The port's current state as defined by application of the Spanning Tree Protocol.  
                      This state controls what action a port takes on reception of a frame.  If the bridge has 
                      detected a port that is malfunctioning it will place that port into the broken(6) state.  
                      For ports which are disabled (see MrstpPortInfoEnable), this object will have a value of 
                      disabled(1)."
              REFERENCE
                      "IEEE 802.1D-1990: Section 4.5.5.2"
              ::= { zyxelMrstpPortInfoEntry 1 }

          zyMrstpPortInfoDesignatedRoot OBJECT-TYPE
              SYNTAX  BridgeId
              MAX-ACCESS  read-only
              STATUS  current
              DESCRIPTION
                      "The unique Bridge Identifier of the Bridge recorded as the Root in the Configuration BPDUs 
                      transmitted by the Designated Bridge for the segment to which the port is attached."
              REFERENCE
                      "IEEE 802.1D-1990: Section 4.5.5.4"
              ::= { zyxelMrstpPortInfoEntry 2 }

          zyMrstpPortInfoDesignatedCost OBJECT-TYPE
              SYNTAX  INTEGER
              MAX-ACCESS  read-only
              STATUS  current
              DESCRIPTION
                      "The path cost of the Designated Port of the segment connected to this port.  This value is 
                      compared to the Root Path Cost field in received bridge PDUs."
              REFERENCE
                      "IEEE 802.1D-1990: Section 4.5.5.5"
              ::= { zyxelMrstpPortInfoEntry 3 }

          zyMrstpPortInfoDesignatedBridge OBJECT-TYPE
              SYNTAX  BridgeId
              MAX-ACCESS  read-only
              STATUS  current
              DESCRIPTION
                      "The Bridge Identifier of the bridge which this port considers to be the Designated Bridge 
                      for this port's segment."
              REFERENCE
                      "IEEE 802.1D-1990: Section 4.5.5.6"
              ::= { zyxelMrstpPortInfoEntry 4 }

          zyMrstpPortInfoDesignatedPort OBJECT-TYPE
              SYNTAX  OCTET STRING (SIZE (2))
              MAX-ACCESS  read-only
              STATUS  current
              DESCRIPTION
                      "The Port Identifier of the port on the Designated Bridge for this port's segment."
              REFERENCE
                      "IEEE 802.1D-1990: Section 4.5.5.7"
              ::= { zyxelMrstpPortInfoEntry 5 }

          zyMrstpPortInfoForwardTransitions OBJECT-TYPE
              SYNTAX  Counter32
              MAX-ACCESS  read-only
              STATUS  current
              DESCRIPTION
                      "The number of times this port has transitioned from the Learning state to the Forwarding state."
              ::= { zyxelMrstpPortInfoEntry 6 }
  
          zyMrstpPortInfoOperEdgePort OBJECT-TYPE
              SYNTAX  INTEGER {
                          true(1),
                          false(2)
                      }
              MAX-ACCESS  read-only
              STATUS  current
              DESCRIPTION
  					  "The operational value of the Edge Port parameter.  The object is initialized to the value of 
  					  the corresponding instance of dot1dStpPortAdminEdgePort.  When the corresponding instance of 
  					  dot1dStpPortAdminEdgePort is set, this object will be changed as well.  This object will also 
  					  be changed to false on reception of a BPDU."
              REFERENCE
                      "IEEE 802.1t clause 14.8.2, 18.3.4"
              ::= { zyxelMrstpPortInfoEntry 7 }
                                                                
--  MRSTP Trap          
	
	 	  zyMrstpNewRoot NOTIFICATION-TYPE
      	  OBJECTS {
       	   zyMrstpBridgeIndex
      	  }
      	  STATUS  current
      	  DESCRIPTION
       	     "The newRoot trap indicates that the sending agent has become the new root of the Spanning Tree; 
       	     the trap is sent by a bridge soon after its election as the new root, e.g., upon expiration of the 
       	     Topology Change Timer, immediately subsequent to its election.  Implementation of this trap is optional."
      	  ::= { zyxelMrstpNotifications 1 }
                                             
    	  zyMrstpTopologyChange NOTIFICATION-TYPE
     	  OBJECTS {
        	 zyMrstpBridgeIndex
      	  }
      	  STATUS  current
      	  DESCRIPTION
       	   "A topologyChange is sent if the topology changed of MRSTP has detected."
     	  ::= { zyxelMrstpNotifications 2 }  
END
